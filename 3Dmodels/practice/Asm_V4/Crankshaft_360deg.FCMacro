# coding: utf-8

# well ... step, in deg°
step = 10

# initial (and final) angle, in deg°
iangle = -45

for angle in range( iangle, 720+iangle+step, step ):
	App.getDocument("asm_V4").PLA_Crankshaft.Placement = App.Placement( App.Vector(0,0,0), App.Rotation( App.Vector(0,1,0), angle ) )
	App.ActiveDocument.recompute()
	FreeCADGui.updateGui()
